(vl-load-com)
(defun lg:num (n) (if (numberp n) (rtos n 2 8) "0"))
(defun lg:q (s) (vl-prin1-to-string (if s s "")))
(defun lg:point (p) (strcat "[" (lg:num (car p)) "," (lg:num (cadr p)) "]"))
(defun lg:points (pts / out) (setq out "") (foreach p pts (setq out (strcat out (if (= out "") "" ",") (lg:point p)))) (strcat "[" out "]"))
(defun lg:boxpts (pts / xs ys) (if pts (progn (setq xs (mapcar 'car pts) ys (mapcar 'cadr pts)) (list (list (apply 'min xs) (apply 'min ys)) (list (apply 'max xs) (apply 'max ys))))))
(defun lg:boxcorners (box) (list (car box) (list (car (cadr box)) (cadr (car box))) (cadr box) (list (car (car box)) (cadr (cadr box)))))
(defun lg:insertpt (p data origin / x y sx sy ang base) (setq sx (if (assoc 41 data) (cdr (assoc 41 data)) 1.0) sy (if (assoc 42 data) (cdr (assoc 42 data)) 1.0) ang (if (assoc 50 data) (cdr (assoc 50 data)) 0.0) base (cdr (assoc 10 data)) x (* sx (- (car p) (car origin))) y (* sy (- (cadr p) (cadr origin)))) (list (+ (car base) (- (* x (cos ang)) (* y (sin ang)))) (+ (cadr base) (+ (* x (sin ang)) (* y (cos ang))))))
(defun lg:bbox (ent / data kind pts center radius major ratio item sub box origin depth next b p1 p2 chord mid off angle corners)
 (setq data (entget ent) kind (cdr (assoc 0 data)) pts nil)
 (cond
  ((= kind "LINE") (setq pts (list (cdr (assoc 10 data)) (cdr (assoc 11 data)))))
  ((member kind '("LWPOLYLINE" "POLYLINE")) (setq pts (lg:poly ent data)) (if (lg:curved ent data) (setq pts (lg:bulgebox ent data pts))))
  ((member kind '("CIRCLE" "ARC")) (setq center (cdr (assoc 10 data)) radius (cdr (assoc 40 data)) pts (list (list (- (car center) radius) (- (cadr center) radius)) (list (+ (car center) radius) (+ (cadr center) radius)))))
  ((= kind "ELLIPSE") (setq center (cdr (assoc 10 data)) radius (distance '(0 0 0) (cdr (assoc 11 data))) pts (list (list (- (car center) radius) (- (cadr center) radius)) (list (+ (car center) radius) (+ (cadr center) radius)))))
  ((member kind '("TEXT" "ATTRIB" "ATTDEF")) (setq box (textbox data) center (cdr (assoc 10 data))) (if box (setq pts (mapcar '(lambda (p) (mapcar '+ p center)) (lg:boxcorners box)))))
  ((= kind "INSERT") (if (< lg:blockdepth 8) (progn (setq lg:blockdepth (1+ lg:blockdepth) item (tblsearch "BLOCK" (cdr (assoc 2 data))) origin (cdr (assoc 10 item)) sub (cdr (assoc -2 item))) (while (and sub (/= "ENDBLK" (cdr (assoc 0 (entget sub))))) (setq box (lg:bbox sub)) (if box (foreach p (lg:boxcorners box) (setq pts (cons (lg:insertpt p data origin) pts)))) (setq sub (entnext sub))) (setq lg:blockdepth (1- lg:blockdepth)))))
 )
 (lg:boxpts pts))
(defun lg:poly (ent data / kind pts next v) (setq kind (cdr (assoc 0 data)) pts nil) (cond ((= kind "LWPOLYLINE") (foreach pair data (if (= (car pair) 10) (setq pts (cons (trans (cdr pair) ent 0) pts)))) (reverse pts)) ((= kind "POLYLINE") (setq next (entnext ent)) (while (and next (= "VERTEX" (cdr (assoc 0 (setq v (entget next)))))) (setq pts (cons (trans (cdr (assoc 10 v)) ent 0) pts) next (entnext next))) (reverse pts))))
(defun lg:curved (ent data / yes next v) (setq yes nil) (foreach pair data (if (and (= (car pair) 42) (/= (cdr pair) 0.0)) (setq yes T))) (if (= "POLYLINE" (cdr (assoc 0 data))) (progn (setq next (entnext ent)) (while (and next (= "VERTEX" (cdr (assoc 0 (setq v (entget next)))))) (if (and (assoc 42 v) (/= (cdr (assoc 42 v)) 0.0)) (setq yes T)) (setq next (entnext next))))) yes)
(defun lg:bulgebox (ent data pts / bulges next v b index p1 p2 dx dy radius center extra closed)
 (setq bulges nil extra pts closed (= 1 (logand 1 (if (assoc 70 data) (cdr (assoc 70 data)) 0))))
 (if (= "LWPOLYLINE" (cdr (assoc 0 data)))
  (progn (setq b nil) (foreach pair data (cond ((= (car pair) 10) (if b (setq bulges (append bulges (list b)))) (setq b 0.0)) ((= (car pair) 42) (setq b (cdr pair))))) (if b (setq bulges (append bulges (list b)))))
  (progn (setq next (entnext ent)) (while (and next (= "VERTEX" (cdr (assoc 0 (setq v (entget next)))))) (setq bulges (append bulges (list (if (assoc 42 v) (cdr (assoc 42 v)) 0.0))) next (entnext next)))))
 (setq index 0)
 (foreach b bulges
  (if (and (/= b 0.0) (or closed (< index (1- (length pts)))))
   (progn (setq p1 (nth index pts) p2 (nth (rem (1+ index) (length pts)) pts) dx (- (car p2) (car p1)) dy (- (cadr p2) (cadr p1)) radius (/ (* (distance p1 p2) (+ 1 (* b b))) (* 4 (abs b))) center (list (- (/ (+ (car p1) (car p2)) 2.0) (* dy (/ (- 1 (* b b)) (* 4 b)))) (+ (/ (+ (cadr p1) (cadr p2)) 2.0) (* dx (/ (- 1 (* b b)) (* 4 b))))))
    (setq extra (append extra (list (list (- (car center) radius) (- (cadr center) radius)) (list (+ (car center) radius) (+ (cadr center) radius)))))))
  (setq index (1+ index)))
 extra)
(defun lg:sample (ent / data kind center radius start end angle i pts) (setq data (entget ent) kind (cdr (assoc 0 data)) center (cdr (assoc 10 data)) radius (cdr (assoc 40 data)) pts nil i 0) (if (member kind '("CIRCLE" "ARC")) (progn (setq start (if (= kind "ARC") (cdr (assoc 50 data)) 0.0) end (if (= kind "ARC") (cdr (assoc 51 data)) (* 2 pi))) (if (<= end start) (setq end (+ end (* 2 pi)))) (repeat 65 (setq angle (+ start (* (- end start) (/ i 64.0))) pts (cons (list (+ (car center) (* radius (cos angle))) (+ (cadr center) (* radius (sin angle)))) pts) i (1+ i))) (reverse pts))))
(defun lg:include (ent) (and (or lg:includeGenerated (not (assoc -3 (entget ent '("LOGEN_LAYOUT"))))) (not (assoc -3 (entget ent '("LOGEN_EXISTING_OUTPUT"))))))
(defun lg:extract (filename / file ss i ent data kind box pts closed eligible curved count warnings)
 (setq file (open filename "w") ss (ssget "_X" '((410 . "Model"))) i 0 count 0 warnings 0 lg:blockdepth 0)
 (write-line (strcat "{\"version\":2,\"units\":" (itoa (getvar "INSUNITS")) ",\"entities\":[") file)
 (if ss (repeat (sslength ss)
 (setq ent (ssname ss i) data (entget ent) kind (cdr (assoc 0 data)) i (1+ i))
 (if (lg:include ent)
 (progn (setq box (vl-catch-all-apply 'lg:bbox (list ent)) pts nil closed nil eligible nil curved nil) (if (vl-catch-all-error-p box) (setq box nil))
 (if box (progn
 (cond ((member kind '("LWPOLYLINE" "POLYLINE")) (setq pts (lg:poly ent data) closed (= 1 (logand 1 (cdr (assoc 70 data)))) curved (lg:curved ent data)) (if curved (setq pts (lg:sample ent)))) ((= kind "LINE") (setq pts (list (cdr (assoc 10 data)) (cdr (assoc 11 data))))) ((member kind '("CIRCLE" "ARC" "ELLIPSE" "SPLINE")) (setq pts (lg:sample ent) closed (= kind "CIRCLE"))))
 (setq eligible (and closed (not curved) (member kind '("LWPOLYLINE" "POLYLINE")) (not (= 8 (logand 8 (if (assoc 70 data) (cdr (assoc 70 data)) 0)))) (>= (length pts) 3)))
 (if (not pts) (setq pts (list (car box) (list (car (cadr box)) (cadr (car box))) (cadr box) (list (car (car box)) (cadr (cadr box))))))
 (if (< count 20000) (progn
 (write-line (strcat (if (> count 0) "," "") "{\"id\":" (lg:q (cdr (assoc 5 data))) ",\"layer\":" (lg:q (cdr (assoc 8 data))) ",\"type\":" (lg:q kind) ",\"points\":" (lg:points pts) ",\"closed\":" (if closed "true" "false") ",\"boundaryEligible\":" (if eligible "true" "false") ",\"bounds\":[" (lg:num (car (car box))) "," (lg:num (cadr (car box))) "," (lg:num (car (cadr box))) "," (lg:num (cadr (cadr box))) "]}") file)
 (setq count (1+ count))) (setq warnings (1+ warnings)))) (setq warnings (1+ warnings)))))))
 (write-line (strcat "],\"unreadableEntities\":" (itoa warnings) "}") file) (close file) (princ))
(defun lg:layer (name color) (if (not (tblsearch "LAYER" name)) (entmake (list '(0 . "LAYER") '(100 . "AcDbSymbolTableRecord") '(100 . "AcDbLayerTableRecord") (cons 2 name) '(70 . 0) (cons 62 color) '(6 . "Continuous")))))
(defun lg:tag (ent id / data) (if (not ent) (progn (princ "Could not create a layout entity.") (exit))) (setq data (entget ent)) (if (not (entmod (append data (list (list -3 (list (if lg:existing-output "LOGEN_EXISTING_OUTPUT" "LOGEN_LAYOUT") (cons 1000 id))))))) (progn (princ "Could not tag layout entity.") (exit))) (setq lg:entitycount (1+ (if lg:entitycount lg:entitycount 0))))
(defun lg:rect (id layer x y w h / entity) (setq entity (entmakex (list '(0 . "LWPOLYLINE") '(100 . "AcDbEntity") (cons 8 layer) '(100 . "AcDbPolyline") '(90 . 4) '(70 . 1) (cons 10 (list x y)) (cons 10 (list (+ x w) y)) (cons 10 (list (+ x w) (+ y h))) (cons 10 (list x (+ y h)))))) (lg:tag entity id))
(defun lg:line (id layer x1 y1 x2 y2 / entity) (setq entity (entmakex (list '(0 . "LINE") (cons 8 layer) (cons 10 (list x1 y1 0.0)) (cons 11 (list x2 y2 0.0))))) (lg:tag entity id))
(defun lg:text (id layer x y ht text / entity) (setq entity (entmakex (list '(0 . "TEXT") '(100 . "AcDbEntity") (cons 8 layer) '(100 . "AcDbText") (cons 10 (list x y 0.0)) (cons 40 ht) (cons 1 text) '(50 . 0.0) '(41 . 1.0) (cons 7 (if (tblsearch "STYLE" "LOGEN_CAD") "LOGEN_CAD" "Standard")) '(72 . 1) (cons 11 (list x y 0.0)) '(100 . "AcDbText") '(73 . 2)))) (lg:tag entity id))
(defun lg:init (/ ss i) (regapp (if lg:existing-output "LOGEN_EXISTING_OUTPUT" "LOGEN_LAYOUT")) (lg:layer "LOGEN_RACKS" 4) (lg:layer "LOGEN_EXISTING_OCCUPANCY" 2) (lg:layer "LOGEN_NEW_RACKS" 30) (lg:layer "LOGEN_NEW_GROUND_STORAGE" 2) (lg:layer "LOGEN_GROUND_MARKINGS" 3) (lg:layer "LOGEN_GROUND_STORAGE" 2) (lg:layer "LOGEN_CLEARANCES" 30) (lg:layer "LOGEN_LAYOUT_LABELS" 7) (lg:layer "LOGEN_GROUND" 2) (lg:layer "LOGEN_GROUND_LABELS" 7) (lg:layer "LOGEN_GANGWAYS" 8) (if (not (tblsearch "STYLE" "LOGEN_CAD")) (entmake '((0 . "STYLE") (100 . "AcDbSymbolTableRecord") (100 . "AcDbTextStyleTableRecord") (2 . "LOGEN_CAD") (70 . 0) (40 . 0.0) (41 . 1.0) (50 . 0.0) (71 . 0) (42 . 2.5) (3 . "txt.shx") (4 . "")))) (setq ss (ssget "_X" (if lg:existing-output '((-3 ("LOGEN_EXISTING_OUTPUT"))) '((-3 ("LOGEN_LAYOUT")))))) (if ss (progn (setq i 0) (repeat (sslength ss) (entdel (ssname ss i)) (setq i (1+ i))))) (princ))

(defun lg:polygon (id layer pts / entity) (setq entity (entmakex (append (list '(0 . "LWPOLYLINE") '(100 . "AcDbEntity") (cons 8 layer) '(100 . "AcDbPolyline") (cons 90 (length pts)) '(70 . 1)) (mapcar '(lambda (p) (cons 10 p)) pts)))) (lg:tag entity id))
(defun lg:textrot (id layer x y ht angle text / entity) (setq entity (entmakex (list '(0 . "TEXT") '(100 . "AcDbEntity") (cons 8 layer) '(100 . "AcDbText") (cons 10 (list x y 0.0)) (cons 40 ht) (cons 1 text) (cons 50 angle) '(41 . 1.0) (cons 7 (if (tblsearch "STYLE" "LOGEN_CAD") "LOGEN_CAD" "Standard")) '(72 . 1) (cons 11 (list x y 0.0)) '(100 . "AcDbText") '(73 . 2)))) (lg:tag entity id))

(defun lg:markline (id layer x1 y1 x2 y2 / entity) (setq entity (entmakex (list '(0 . "LINE") (cons 8 layer) '(62 . 3) '(420 . 2278750) '(370 . 15) (cons 10 (list x1 y1 0.0)) (cons 11 (list x2 y2 0.0))))) (lg:tag entity id))
